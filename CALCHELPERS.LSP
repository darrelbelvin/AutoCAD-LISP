(defun calcfooting (/ tmp)
    (if (null global:calcfootingint)
        (setq global:calcfootingint 1500)
    )
    (initget 6)
    (if (setq tmp (getint (strcat "Enter a load in lbs <" (itoa global:calcfootingint) ">: ")))
        (setq global:calcfootingint tmp)
    )
    
    (/ (1+ (fix (* 2 (sqrt (/ (+ 1 global:calcfootingint) 1500.0))))) 2.0) ; sqrt((load)/1500) rounded up to nearest 1/2
)

(defun c:calcfooting (/ c)
    (setq c (calcfooting))
    (princ "Footing Size Required (assuming 1500lb/sf bearing): ")
    (princ (rtos (* 12 c)))
    (princ)
)

(defun c:drawfooting (/ *error* main doc l ls lhalf)
    (vl-load-com)
    (defun main ()
        (vla-StartUndoMark (setq doc (vla-get-ActiveDocument (vlax-get-acad-object))))

        (command "-layer" "Thaw" "FN-FOOTING" "Set" "FN-FOOTING" "")
        (setq l (calcfooting)
            ls (rtos (* 12 l))
            lhalf (rtos (* 6 l))
        )
        (princ "Footing Size Required (assuming 1500lb/sf bearing): ")
        (princ ls)
        (command ".polygon" "4" pause "c" lhalf)
        ;(command ".rectangle" pause "Dimensions" l l)
        
        (vla-EndUndoMark doc)
        (princ)
    )
    (defun *error*(s)
        (princ s)
        (vla-EndUndoMark doc)
        (princ)
    )
    (main)
)
