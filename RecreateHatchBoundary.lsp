(defun c:RHB (/ *error* main doc OLDCE SSET CNT OBJ)
  (vl-load-com)
  (defun main ()
    (vla-StartUndoMark (setq doc (vla-get-ActiveDocument (vlax-get-acad-object))))
    
    (setq OLDCE (getvar "cmdecho"))
    (setvar "cmdecho" 0)
    (princ "\nSelect Hatch Objects: ")
    (setq SSET (ssget))
    (setq CNT -1)
    (while (setq OBJ (ssname SSET (setq CNT (1+ CNT))))
      (command "-hatchedit" OBJ "b" "p" "y")
      )
      (setvar "cmdecho" OLDCE)
      (princ)
    
    (vla-EndUndoMark doc)
    (princ)
  )
  (defun *error*(s)
    (princ s)
    (vla-EndUndoMark doc)
    (princ)
  )
  (main)
)
