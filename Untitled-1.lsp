(defun c:aaa (/ *error* main doc)
	(vl-load-com)
	(defun main ()
		(vla-StartUndoMark (setq doc (vla-get-ActiveDocument (vlax-get-acad-object))))
		(setq ss (ssget "_I"))
		(repeat (setq i (sslength ss))
			(setq ed (entget (ssname ss (setq i (1- i)))))
			(setq z (atof (car (LM:str->lst (car (cdr (LM:str->lst (cdr (assoc 1 ed)) ";"))) "}"))))
			(setq ed (subst (list 10 (+ (cadr (assoc 10 ed)) -0.5536) (caddr (assoc 10 ed)) z) (assoc 10 ed) ed))
			(print ed)
			(entmod ed)
		)
		(vla-EndUndoMark doc)
		(princ)
	)
	(defun *error*(s)
		(princ s)
		(vla-EndUndoMark doc)
		(princ)
	)
	(main)
)

(defun c:aaa (/ *error* main doc)
	(vl-load-com)
	(defun main ()
		(vla-StartUndoMark (setq doc (vla-get-ActiveDocument (vlax-get-acad-object))))
		(setq ss (ssget "_I"))
		(repeat (setq i (sslength ss))
			(setq ed (entget (ssname ss (setq i (1- i)))))
			(entmake (list '(0 . "POINT") (assoc 10 ed) (assoc 8 ed)))
		)
		(vla-EndUndoMark doc)
		(princ)
	)
	(defun *error*(s)
		(princ s)
		(vla-EndUndoMark doc)
		(princ)
	)
	(main)
)

(defun LM:str->lst ( str del / pos )
  (if (setq pos (vl-string-search del str))
    (cons (substr str 1 pos) (LM:str->lst (substr str (+ pos 1 (strlen del))) del))
    (list str)
  )
)
